module vehicle {
    yang-version 1;
    namespace "urn:opendaylight:params:xml:ns:yang:vehicle";
    prefix "vehicle";

    revision "2015-01-05" {
        description "Initial revision of vehicle model";
    }
}
